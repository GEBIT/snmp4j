SNMP4J-PROXY-MIB DEFINITIONS ::= BEGIN

IMPORTS
	snmp4jAgentModules
		FROM SNMP4J-AGENT-REG
	SnmpAdminString,
	SnmpEngineID
		FROM SNMP-FRAMEWORK-MIB
	StorageType,
	RowStatus
		FROM SNMPv2-TC
	zeroDotZero,
	MODULE-IDENTITY,
	OBJECT-TYPE
		FROM SNMPv2-SMI
	OBJECT-GROUP
		FROM SNMPv2-CONF;

snmp4jProxyMIB MODULE-IDENTITY
	LAST-UPDATED "201107300851Z"	-- Jul 30, 2011 8:51:00 AM
	ORGANIZATION "SNMP4J.org"
	CONTACT-INFO
		"Frank Fock
		E-Mail: fock@snmp4j.org
		Postal: AGENT++
		      Maximilian-Kolbe-Str. 10
		      73257 Koengen
		      Germany"
	DESCRIPTION
		"This MIB module defines MIB objects for the
		remote configuration of subtree proxy 
		applications properties.

		Copyright (C) Frank Fock (2011). All rights reserved.

		"
	REVISION "201107300851Z"	-- Jul 30, 2011 8:51:00 AM
	DESCRIPTION
		"Added snmp4jProxyTargetSubtree"
	REVISION "201104172315Z"	-- Apr 17, 2011 11:15:00 PM
	DESCRIPTION
		"Initial version."
	-- 1.3.6.1.4.1.4976.10.1.1.3
	::= { snmp4jAgentModules 3 }


-- Scalars and Tables
--

snmp4jProxyObjects OBJECT IDENTIFIER 
	-- 1.3.6.1.4.1.4976.10.1.1.3.1
	::= { snmp4jProxyMIB 1 }

snmp4jProxyTable OBJECT-TYPE
	SYNTAX  SEQUENCE OF Snmp4jProxyEntry
	MAX-ACCESS not-accessible
	STATUS  current
	DESCRIPTION
		"The table of translation parameters used to
		proxy requests for a specified object identifier
		sub-tree."
	-- 1.3.6.1.4.1.4976.10.1.1.3.1.1
	::= { snmp4jProxyObjects 1 }


snmp4jProxyEntry OBJECT-TYPE
	SYNTAX  Snmp4jProxyEntry
	MAX-ACCESS not-accessible
	STATUS  current
	DESCRIPTION
		"A set of translation parameters used by a proxy 
		sub-tree for forwarding SNMP messages.

		Entries in the snmp4jProxyTable are created and 
		deleted using the snmp4jProxyRowStatus object."
	INDEX {
 		IMPLIED snmp4jProxyName }
	-- 1.3.6.1.4.1.4976.10.1.1.3.1.1.1
	::= { snmp4jProxyTable 1 }


Snmp4jProxyEntry ::= SEQUENCE {

	snmp4jProxyName            SnmpAdminString,
	snmp4jProxyContextEngineID SnmpEngineID,
	snmp4jProxyContextName     OCTET STRING,
	snmp4jProxySubtree         OBJECT IDENTIFIER,
	snmp4jProxyType            INTEGER,
	snmp4jProxyTarget          SnmpAdminString,
	snmp4jProxyStorageType     StorageType,
	snmp4jProxyRowStatus       RowStatus,
	snmp4jProxyTargetSubtree   OBJECT IDENTIFIER }


snmp4jProxyName OBJECT-TYPE
	SYNTAX  SnmpAdminString (SIZE (1..32))
	MAX-ACCESS not-accessible
	STATUS  current
	DESCRIPTION
		""
	-- 1.3.6.1.4.1.4976.10.1.1.3.1.1.1.1
	::= { snmp4jProxyEntry 1 }


snmp4jProxyContextEngineID OBJECT-TYPE
	SYNTAX  SnmpEngineID
	MAX-ACCESS read-create
	STATUS  current
	DESCRIPTION
		"The contextEngineID contained in messages
		that may be forwarded using the translation
		parameters defined by this entry.
		The default value is the zero length string which
		always matches the agent's own authoritative
		engine ID."
	-- 1.3.6.1.4.1.4976.10.1.1.3.1.1.1.2
	::= { snmp4jProxyEntry 2 }


snmp4jProxyContextName OBJECT-TYPE
	SYNTAX  OCTET STRING (SIZE (0..255))
	MAX-ACCESS read-create
	STATUS  current
	DESCRIPTION
		"The context name for this proxy subtree. If it is
		set to the zero length string, then the proxy subtree
		will be registered with all contexts in the agent."
	DEFVAL { "" }
	-- 1.3.6.1.4.1.4976.10.1.1.3.1.1.1.3
	::= { snmp4jProxyEntry 3 }


snmp4jProxySubtree OBJECT-TYPE
	SYNTAX  OBJECT IDENTIFIER
	MAX-ACCESS read-create
	STATUS  current
	DESCRIPTION
		"The OID of the sub-tree which is subject to this proxy.
		The agent will forward requests for this sub-tree
		to the target identified by snmp4jProxyTarget."
	-- 1.3.6.1.4.1.4976.10.1.1.3.1.1.1.4
	::= { snmp4jProxyEntry 4 }


snmp4jProxyType OBJECT-TYPE
	SYNTAX  INTEGER {
			invalid(0),
			readAndWrite(1),
			readOnly(2),
			noProxy(3) }
	MAX-ACCESS read-create
	STATUS  current
	DESCRIPTION
		"Defines the type messages that are forwarded
		on behalf of this sub-tree proxy. 'readOnly(2)' forwards
		only read messages like GET, GETNEXT, GETBULK.
		'noProxy(3)' does not forward any messages at all.
		'readAndWrite(1)' is the default and forwards any 
		read or write message (i.e. SET requests).
		The status value 'invalid(0)' cannot be set. It indicates
		that the sub-tree proxy cannot be defined because
		the sub-tree overlaps with an already registered
		managed object."
	DEFVAL { readAndWrite }
	-- 1.3.6.1.4.1.4976.10.1.1.3.1.1.1.5
	::= { snmp4jProxyEntry 5 }


snmp4jProxyTarget OBJECT-TYPE
	SYNTAX  SnmpAdminString
	MAX-ACCESS read-create
	STATUS  current
	DESCRIPTION
		"This object selects a management target defined in the
		snmpTargetAddrTable (in the SNMP-TARGET-MIB).  The
		selected target is defined by an entry in the
		snmpTargetAddrTable whose index value 
		(snmpTargetAddrName) is equal to this object."
	-- 1.3.6.1.4.1.4976.10.1.1.3.1.1.1.6
	::= { snmp4jProxyEntry 6 }


snmp4jProxyStorageType OBJECT-TYPE
	SYNTAX  StorageType
	MAX-ACCESS read-create
	STATUS  current
	DESCRIPTION
		"The storage type of this conceptual row.
		Conceptual rows having the value 'permanent' 
		need not allow write-access to any columnar 
		objects in the row."
	-- 1.3.6.1.4.1.4976.10.1.1.3.1.1.1.7
	::= { snmp4jProxyEntry 7 }


snmp4jProxyRowStatus OBJECT-TYPE
	SYNTAX  RowStatus
	MAX-ACCESS read-create
	STATUS  current
	DESCRIPTION
		"The status of this conceptual row.

		To create a row in this table, a manager must
		set this object to either createAndGo(4) or
		createAndWait(5).

		The following objects may not be modified while the
		value of this object is active(1):
		- snmp4jProxyContextName
		- snmp4jProxyContextEngineID
		- snmp4jProxyType
		- snmpProxyTarget

		"
	-- 1.3.6.1.4.1.4976.10.1.1.3.1.1.1.8
	::= { snmp4jProxyEntry 8 }


snmp4jProxyTargetSubtree OBJECT-TYPE
	SYNTAX  OBJECT IDENTIFIER
	MAX-ACCESS read-create
	STATUS  current
	DESCRIPTION
		"To translate between two different sub-trees (local 
		and remote), the target sub-tree object identifier
		can be specified. 
		For example 1.3.6.1.4.1.4976.10.1.1.3 in the local
		agent can be provided by a sub-tree 1.3.6.1.4.1.49976.1.1.1
		by a remote agent.
		To deactivate translation set the value to zeroDotZero (0.0)."
	DEFVAL { zeroDotZero }
	-- 1.3.6.1.4.1.4976.10.1.1.3.1.1.1.9
	::= { snmp4jProxyEntry 9 }


-- Notification Types
--

snmp4jProxyEvents OBJECT IDENTIFIER 
	-- 1.3.6.1.4.1.4976.10.1.1.3.2
	::= { snmp4jProxyMIB 2 }

-- Conformance
--

snmp4jProxyConf OBJECT IDENTIFIER 
	-- 1.3.6.1.4.1.4976.10.1.1.3.3
	::= { snmp4jProxyMIB 3 }

-- Groups
--

snmp4jProxyGroups OBJECT IDENTIFIER 
	-- 1.3.6.1.4.1.4976.10.1.1.3.3.1
	::= { snmp4jProxyConf 1 }

-- Compliance
--

snmp4jProxyCompls OBJECT IDENTIFIER 
	-- 1.3.6.1.4.1.4976.10.1.1.3.3.2
	::= { snmp4jProxyConf 2 }

snmp4jProxyBasicGroup OBJECT-GROUP
	OBJECTS {
		snmp4jProxyContextEngineID,
		snmp4jProxyContextName,
		snmp4jProxySubtree,
		snmp4jProxyType,
		snmp4jProxyTarget,
		snmp4jProxyStorageType,
		snmp4jProxyRowStatus }
	STATUS  current
	DESCRIPTION
		"Basic objects for sub-tree based proxy forwarding."
	-- 1.3.6.1.4.1.4976.10.1.1.3.3.1.1
	::= { snmp4jProxyGroups 1 }

snmp4jProxyExtendedGroup OBJECT-GROUP
	OBJECTS {
		snmp4jProxyTargetSubtree }
	STATUS  current
	DESCRIPTION
		"This group contains advanced objects to control
		proxy operations."
	-- 1.3.6.1.4.1.4976.10.1.1.3.3.1.2
	::= { snmp4jProxyGroups 2 }

END
