OOSNMP-USM-MIB DEFINITIONS ::= BEGIN

IMPORTS
	agentppGeneric
		FROM AGENTPP-GLOBAL-REG
	MODULE-IDENTITY
		FROM SNMPv2-SMI;

oosnmpMIB MODULE-IDENTITY
	LAST-UPDATED "200911242212Z"	-- Nov 24, 2009 10:12:00 PM
	ORGANIZATION "oosnmp.com"
	CONTACT-INFO
		"Frank Fock
		 E-Mail: info@oosnmp.com"
	DESCRIPTION
		"This MIB module defines objects for the user based
		security module (USM) of the SNMPv3 framework
		which are not covered by the SNMP standard."
	REVISION "200911242212Z"	-- Nov 24, 2009 10:12:00 PM
	DESCRIPTION
		"Initial version."
	-- 1.3.6.1.4.1.4976.2.2
	::= { agentppGeneric 2 }


-- Scalars and Tables
--

oosnmpObjects OBJECT IDENTIFIER 
	-- 1.3.6.1.4.1.4976.2.2.1
	::= { oosnmpMIB 1 }

oosnmpUSM OBJECT IDENTIFIER 
	-- 1.3.6.1.4.1.4976.2.2.1.1
	::= { oosnmpObjects 1 }

oosnmpUsmAesCfb192Protocol OBJECT IDENTIFIER 
	-- 1.3.6.1.4.1.4976.2.2.1.1.1
	::= { oosnmpUSM 1 }

oosnmpUsmAesCfb256Protocol OBJECT IDENTIFIER 
	-- 1.3.6.1.4.1.4976.2.2.1.1.2
	::= { oosnmpUSM 2 }

-- Notification Types
--

oosnmpEvents OBJECT IDENTIFIER 
	-- 1.3.6.1.4.1.4976.2.2.2
	::= { oosnmpMIB 2 }

-- Conformance
--

oosnmpConf OBJECT IDENTIFIER 
	-- 1.3.6.1.4.1.4976.2.2.3
	::= { oosnmpMIB 3 }

-- Groups
--

oosnmpGroups OBJECT IDENTIFIER 
	-- 1.3.6.1.4.1.4976.2.2.3.1
	::= { oosnmpConf 1 }

-- Compliance
--

oosnmpCompls OBJECT IDENTIFIER 
	-- 1.3.6.1.4.1.4976.2.2.3.2
	::= { oosnmpConf 2 }

END
